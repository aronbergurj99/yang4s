module example2 {
    namespace "http://aronj.is/example2";
    prefix "example2";

    typedef test-type {
        type string;
    }

    container hello {
        leaf world {
            type string;
        }
    }
}
