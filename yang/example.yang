module example {
    namespace "http://aronj.is/example";
    prefix "example";

    import example2 {
        prefix example2;
    }

    import ietf-yang-types {
        prefix yang;
    }

    typedef third {
        type string;
    }

    typedef hostname {
        type another;
    }
    typedef another {
        type third;
    }

    container interfaces {
        list TenGigE {
            key name;
            leaf name {
                type example2:test-type;
            }
        }
    }

    container first {
        list second {
            key hostname;
            leaf hostname {
                type hostname;
            }
            leaf time {
                type yang:timestamp;
            }
            container third;
        }
    }
}
